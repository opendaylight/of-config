module odl-ofconfig-node-inventory {
    namespace "urn:opendaylight:odl-ofconfig-node-inventory";
    prefix "ofconfiginv";

    import opendaylight-inventory {
        prefix inv;
        revision-date "2013-08-19";
    }

    import yang-ext {
        prefix ext;
        revision-date "2013-07-09";
    }

    import ietf-inet-types {
        prefix inet;
        revision-date "2010-09-24";
    }


    import odl-ofconfig-types { 
    	prefix "odl-ofconfig-types"; 
    	revision-date "2015-09-01";
    }

    revision "2015-09-17" {
        description "Initial revision of the OF-CONFIG Inventory model";
    }

    grouping ofconfig-logical-switch-attributes {
        leaf logical-switch-dpid {
            type string;
        }

        leaf logical-switch-id {
            type string;
        }

        leaf managed-by {
            type inv:node-id;
        }
    }

    grouping ofconfig-capable-switch-attributes {
        leaf ip-address {
            description "The IP Address of an ofconfig capable switch node";
            type inet:ip-address;
        }

        leaf port {
            description "The port that an ofconfig capable switch node is connected on";
            type inet:port-number;
        }
        
        leaf ofconfig-version {
	            type identityref {
	                base odl-ofconfig-types:of-config-version-type-base;
	            }
	     }

        leaf-list managed-nodes {
            type inv:node-id;
        }
    }

    augment /inv:nodes/inv:node {
        ext:augment-identifier "ofconfig-logical-switch-node";
        // when "/inv:nodes/inv:node/flowcapable:manufacturer = '*'";
        container ofconfig-logical-switch {
            uses ofconfig-logical-switch-attributes;
        }
    }

    augment /inv:nodes/inv:node {
        ext:augment-identifier "ofconfig-capable-switch-node";
        uses ofconfig-capable-switch-attributes;
    }

}

module odl-ofconfig12 {
    yang-version 1;
    namespace "urn:opendaylight:params:xml:ns:yang:ofconfig12";
    prefix "ofconfig12";

    
    import ietf-inet-types { prefix inet; revision-date 2013-07-15; }
    import ietf-yang-types { prefix yang; revision-date "2013-07-15";}
    import of-config{ prefix of-config; revision-date "2014-06-01";}

    revision "2015-09-01" {
        description "Initial revision of opendaylight of-config topology";
    }
    
    grouping capable-switch-node-attributes{
    
    	container capable-switch{
    		uses of-config:CapableSwitchType;
    	
    	}
    }
    
    
   
    
    grouping of-config-logical-switch-attributes{
    
    	container logical-switch{
    		uses of-config:OFLogicalSwitchType;
    	}
    		
    }

    grouping of-config-xurong {

    	container logical-switch{
    		//uses of-config:OFLogicalSwitchType;
    	}

    }

    
    
    
}

module odl-ofconfig-api {
    yang-version 1;
    namespace "urn:opendaylight:params:xml:ns:yang:ofconfig:base:api";
    prefix "odl-ofconfig-base-api";
    
     revision "2015-09-01" {
        description "Initial revision of opendaylight of-config base api";
    }
    
    
     rpc sync_capcable_switch{
    
    	input {
            leaf node-id {
                mandatory true;
                type string;
                description
                    "id of the of-config capable switch node to be displayed";
            }
        }
    }
    
    rpc query_logical_switch_node_id{
    
    	input {
            leaf datapath-id {
                mandatory true;
                type string;
                description
                    "logical switch datapath-id";
            }
        }
        output{
        	leaf node-id {
        		 type string;
        		  description
                    "id of the of-config logical switch node to be displayed";
        	}
        
        }
    
    }
    
    
    
}
